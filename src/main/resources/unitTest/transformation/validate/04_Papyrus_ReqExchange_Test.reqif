Transformed by ReqExchange from SysML

# Specification: 04_Papyrus_ReqExchange
- Description: Requirement Document

## 01: Systemvorraussetzung
Das Ziel-Betriebssystem für ReqExchange Client und ReqExchange Server ist Windows 10.

## 04: Synchronisation
Es soll möglich sein, weitere Formate in die Architektur einzubinden.

### 04a: Senden
Der Nutzer kann Änderungen an Requirement Dateien mit Hilfe des ReqExchange Clients an den ReqExchange Server senden. Zuvor werden die Änderungen in das definierte Metamodell überführt.

### 04b: Empfangen
Der Nutzer kann Änderungen an Requirement Dateien von anderen Nutzern mit Hilfe des ReqExchange Clients vom ReqExchange Server empfangen.

### 04c1: Konflikte
Der Nutzer kann Änderungen an Requirement Dateien von anderen Nutzern mit Hilfe des ReqExchange Clients vom ReqExchange Server empfangen.

### 04d: Zusammenfügen von unabhängigen Änderungen
Der Nutzer kann Änderungen an Requirement Dateien von anderen Nutzern mit Hilfe des ReqExchange Clients vom ReqExchange Server empfangen.

## 09: Effiziente Kommunikation
Der ReqExchange Client markiert ein Projekt, wenn auf dem Client Änderungen an einem Projekt zum versenden verfügbar sind.

## 08: Synchronisationshinweis empfangen
Der ReqExchange Client markiert ein Projekt, wenn auf dem Client Änderungen an einem Projekt zum versenden verfügbar sind.

## 05: Metamodell
Es wird ein einheintliches Metamodell für die Requirementrepräsentation auf dem ReqExchange Server verwendet. Änderungen an Requirement Dateien werden von dem ReqExchange Client in dieses Modell überführt.

## 07: Synchronisationshinweis senden
Der ReqExchange Client markiert ein Projekt, wenn auf dem Client Änderungen an einem Projekt zum versenden verfügbar sind.

## 02: Projektverwaltung
Der ReqExchange Client erlaubt dem Nutzer, Requirements Projekte zu verwalten.

### 02a: Erstellung
Der Nutzer kann mit Hilfe des ReqExchange-Client ein Projekt erstellen. Dafür muss der Nutzer eine Bezeichnung und ein Passwort angeben. Des Weiteren muss eine Datei im ReqIF-Format angegeben werden, dessen Requirements initial importiert werden.

### 02b: Beitritt
Der Nutzer kann mithilfe des Passworts einem bestehenden Projekt beitreten.

### 02c: Generierung
Der Nutzer kann mithilfe des Passworts einem bestehenden Projekt beitreten.

### 02d: Änderung
Der Nutzer kann mithilfe des Passworts einem bestehenden Projekt beitreten.

## 03: Requirement Export
Der Nutzer kann mithilfe des Passworts einem bestehenden Projekt beitreten.

### 03a: ReqIF
Der Nutzer kann mithilfe des Passworts einem bestehenden Projekt beitreten.

### 03b: Microsoft Office Excel
Der Nutzer kann mithilfe des Passworts einem bestehenden Projekt beitreten.

### 03c: Papyrus SysML
"Requirement Dateien im (.di, .uml, .notation) Format werden durch den ReqExchange Client unterstützt.
"

### 03d: Microsoft Office Word
Microsoft Office Word Dateien im Format .docx werden vom ReqExchange Client unterstützt.

### 03e: Erweiterbarkeit
Es soll möglich sein, weitere Formate in die Architektur einzubinden.

## 04c2: Konflikte Erweitert
Der Nutzer kann Änderungen an Requirement Dateien von anderen Nutzern mit Hilfe des ReqExchange Clients vom ReqExchange Server empfangen.
