# Specification: Specification Document
- Description: Requirements Document

## R1: Systemvorraussetzung (Requirement Type)
Das Ziel-Betriebssystem für ReqExchange Client und ReqExchange Server ist Windows 10.

## R3: Projektverwaltung (Requirement Type)
Der ReqExchange Client erlaubt dem Nutzer, Requirements Projekte zu verwalten.

### R4: Erstellung (Requirement Type)
Der Nutzer kann mit Hilfe des ReqExchange-Client ein Projekt erstellen. Dafür muss der Nutzer eine Bezeichnung und ein Passwort angeben. Des Weiteren muss eine Datei im ReqIF-Format angegeben werden, dessen Requirements initial importiert werden.

### R5: Beitritt (Requirement Type)
Der Nutzer kann mithilfe des Passworts einem bestehenden Projekt beitreten.

### R6: Generierung (Requirement Type)
Der Nutzer kann sich mit Hilfe des ReqExchange Clients vom ReqExchange Server abgerufene Requirement Dateien in unterstützten Formaten generieren lassen.

### R7: Änderung (Requirement Type)
Der Nutzer kann mit Hilfe des ReqExchange-Client die Eigenschaften Bezeichnung und Passwort eines Projektes ändern. Außerdem kann der Nutzer Projekte löschen.

## R8: Requirement Export (Requirement Type)
Nur Requirement Dateien, die in einem durch den ReqExchange Client Unterstützten Format vorliegen, können Exportiert und zur Bearbeitung der Requirements verwendet werden.

### R10: ReqIF (Requirement Type)
"Requirement Dateien im ReqIF Format werden durch den ReqExchange Client unterstützt.
"

### R11: Microsoft Office Excel (Requirement Type)
"Microsoft Office Excel Dateien im Format .xlsx werden vom ReqExchange Client unterstützt.
"

### R12: Papyrus SysML (Requirement Type)
"Requirement Dateien im ReqIF Format werden durch den ReqExchange Client unterstützt.
"

### R13: Microsoft Office Word (Requirement Type)
Microsoft Office Word Dateien im Format .docx werden vom ReqExchange Client unterstützt.

### R14: Erweiterbarkeit (Requirement Type)
Es soll möglich sein, weitere Formate in die Architektur einzubinden.

## R16: Synchronisation (Requirement Type)
Die Requirements werden vom ReqExchange Client mit dem Server synchronisiert.

### R17: Senden (Requirement Type)
Der Nutzer kann Änderungen an Requirement Dateien mit Hilfe des ReqExchange Clients an den ReqExchange Server senden. Zuvor werden die Änderungen in das definierte Metamodell überführt.

### R18: Empfangen (Requirement Type)
Der Nutzer kann Änderungen an Requirement Dateien mit Hilfe des ReqExchange Clients an den ReqExchange Server senden. Zuvor werden die Änderungen in das definierte Metamodell überführt.

#### R22: Konflikte (Requirement Type)
Der Nutzer kann Änderungen an Requirement Dateien mit Hilfe des ReqExchange Clients an den ReqExchange Server senden. Zuvor werden die Änderungen in das definierte Metamodell überführt.

#### R23: Konflikte - Erweitert (Requirement Type)
Dem Nutzer werden Konflikte angezeigt und der Nutzer kann eine Version wählen.

### R24: Zusammenfügen von unabhängigen Änderungen (Requirement Type)
Werden voneinander unabhängige Änderungen an den ReqExchange Server gesendet, sollen die Änderungen automatisch zusammengefügt werden.

## R25: Metamodell (Requirement Type)
Es wird ein einheintliches Metamodell für die Requirementrepräsentation auf dem ReqExchange Server verwendet. Änderungen an Requirement Dateien werden von dem ReqExchange Client in dieses Modell überführt.

## R26: Synchronisationshinweis senden (Requirement Type)
Der ReqExchange Client markiert ein Projekt, wenn auf dem Client Änderungen an einem Projekt zum versenden verfügbar sind.

## R27: Synchronisationshinweis empfangen (Requirement Type)
Der ReqExchange Client markiert ein Projekt, wenn auf dem Server Änderungen an einem Projekt zum abrufen verfügbar sind.

## R28: Effiziente Kommunikation (Requirement Type)
Bei dem Senden von Requirement Dateien an den ReqExchange Servern sollen nur die Änderungen an Requirement Dateien gesendet werden, um möglichst wenig Traffic zu erzeugen und performant zu arbeiten.

## R2 (Requirement Type)

## R9 (Requirement Type)

## R15

## R19 (Requirement Type)

## R20

## R21
